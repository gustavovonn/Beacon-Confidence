PCM-PDU-Descriptions {
itu-t (0) identified-organization (4) etsi (0) itsDomain (5) wg1 (1) en (302633) pcm (2) version (2)
}

DEFINITIONS AUTOMATIC TAGS ::=

BEGIN

IMPORTS
ItsPduHeader, ReferencePosition, AccelerationControl, Curvature, CurvatureCalculationMode, Heading, LanePosition, Speed, DriveDirection, LongitudinalAcceleration, LateralAcceleration, VerticalAcceleration, StationType, VehicleLength, VehicleWidth, SteeringWheelAngle, PerformanceClass, YawRate, Latitude, Longitude, CenDsrcTollingZone FROM ITS-Container {
itu-t (0) identified-organization (4) etsi (0) itsDomain (5) wg1 (1) ts (102894) cdd (2) version (2)
}
GenerationDeltaTime, BasicContainer FROM CAM-PDU-Descriptions { itu-t(0) identified-organization(4) etsi(0) itsDomain(5) wg1(1) en(302637) cam(2) version(2)} ;


--  The root data frame for cooperative awareness messages

TSTP ::= SEQUENCE {
    header ItsPduHeader,
    tstp TSTPContent
}

TSTPContent ::= SEQUENCE {
    generationDeltaTime GenerationDeltaTime,
    tstpParameters TSTPParameters
}

TSTPParameters ::= SEQUENCE {
    messageType INTEGER (0..255),
    messageID INTEGER (0..255),
    content OCTET STRING(SIZE(1..512)),
    basicContainer BasicContainer
}


END
