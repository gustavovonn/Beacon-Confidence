PCM-PDU-Descriptions {
itu-t (0) identified-organization (4) etsi (0) itsDomain (5) wg1 (1) en (302633) pcm (2) version (2)
}

DEFINITIONS AUTOMATIC TAGS ::=

BEGIN

IMPORTS
ItsPduHeader, ReferencePosition, AccelerationControl, Curvature, CurvatureCalculationMode, Heading, LanePosition, Speed, DriveDirection, LongitudinalAcceleration, LateralAcceleration, VerticalAcceleration, StationType, VehicleLength, VehicleWidth, SteeringWheelAngle, PerformanceClass, YawRate, Latitude, Longitude, CenDsrcTollingZone FROM ITS-Container {
itu-t (0) identified-organization (4) etsi (0) itsDomain (5) wg1 (1) ts (102894) cdd (2) version (2)
}
GenerationDeltaTime, BasicContainer, HighFrequencyContainer FROM CAM-PDU-Descriptions { itu-t(0) identified-organization(4) etsi(0) itsDomain(5) wg1(1) en(302637) cam(2) version(2)} ;


--  The root data frame for cooperative awareness messages

PCM ::= SEQUENCE {
    header ItsPduHeader,
    pcm PerceptionConsensus
}

PerceptionConsensus ::= SEQUENCE {
    generationDeltaTime GenerationDeltaTime,
    pcmParameters PcmParameters
}

PcmParameters ::= SEQUENCE {
    consensusStep INTEGER (0..255),
    messageCounter INTEGER (0..255),
    basicContainer BasicContainer,
    highFrequencyContainer HighFrequencyContainer
}


END
